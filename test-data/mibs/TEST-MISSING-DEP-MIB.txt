TEST-MISSING-DEP-MIB DEFINITIONS ::= BEGIN

-- Imports from a module that is deliberately NOT part of this fixture set.
-- Loading it on its own must surface "Missing MIB dependencies:
-- TEST-ABSENT-MIB" on the file and leave the rest of the tree intact.

IMPORTS
    MODULE-IDENTITY, OBJECT-TYPE, Integer32
        FROM SNMPv2-SMI
    absentAnchor
        FROM TEST-ABSENT-MIB;

testMissingDepMIB MODULE-IDENTITY
    LAST-UPDATED "202601010000Z"
    ORGANIZATION "MIB Browser Test Data"
    CONTACT-INFO
        "https://github.com/shmuto/mib-browser"
    DESCRIPTION
        "Hangs off a node defined in a module that is not supplied."
    ::= { absentAnchor 1 }

danglingLeaf OBJECT-TYPE
    SYNTAX      Integer32
    MAX-ACCESS  read-only
    STATUS      current
    DESCRIPTION "Unreachable until TEST-ABSENT-MIB is loaded."
    ::= { testMissingDepMIB 1 }

END
